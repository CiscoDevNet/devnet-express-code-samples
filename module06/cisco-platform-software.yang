module cisco-platform-software {

     yang-version 1;

     namespace "urn:cisco:params:xml:ns:yang:cisco-platform-software";
     prefix platform-software;


     organization
    "Cisco Systems, Inc.";

   contact
    " Cisco Systems, Inc.
    Customer Service

    Postal: 170 W Tasman Drive
    San Jose, CA 95134

    Tel: +1 1800 553-NETS

    E-mail: cs-yang@cisco.com";
    
    description
       "This module contains a collection of YANG definitions for
        monitoring the platform software in a Network Element.";
    
    reference "TODO";
    
    revision 2015-07-09 {
    description "added platform-software-interface-RP-active-brief-Forwarding"; 
  }

    revision 2015-05-20 {
    description "Proposed";  
  }
  
	container platform-software-status-control-process {
		config false;
		description
			"Contents of the show platform software status control process cli.";
	
                list control-process {
                        key "name";
                        description
                                "Control process";

                leaf name {
                        type string;
                        description
                                "Name of the control process";
                }
 
		leaf status {
			type string;
        	description
        		"Status of the control processer";
		}
		
		leaf updated {
			type uint8;
			description
				"Number of seconds since the data has been updated.";
		}
		
		container load-average-stats {
			description
				"Statistics on the load average.";
				
			leaf load-average-status {
				type string;
        	}
        	
        	list minutes {
        		key "number";
        		description
        			"Load average statistics based on a time frame";
        		
        		leaf number {
        			type uint8;
        			description
        				"The number of minutes the average was calculated on.";
        		}
        		
        		leaf average {
        			type decimal64 {
	    				fraction-digits 2;
	    			}
        			description
        				"NEED description";
        		}

                	container status {

                	leaf condition {
                        	type string;
                        	description
                                	"Need description";
                	}

                	leaf threshold-status {
                        	type string;
                        	description
                                	"Need description";
                	}

                	leaf threshold-value {
                        	type decimal64 {
                                        fraction-digits 2;
                                }
                        	description
                                	"Need description";
                	}

                	}        		
        		
        	}
        	
		}
		
		container memory-stats {
			description
				"The statistics on the memory";
				
    		leaf memory-status {
    			type string;
    			description
    				"The status of the memory";
    		}
    		
    		leaf total {
    			type uint32;
    			description
    				"The total number of memory in kb";
    		}
    		
    		leaf used-number {
    			type uint32;
    			description
    				"The number of memory being used in kb";
    		}
    		
    		leaf used-percent {
    			type uint8;
    			description
    				"The percentage of memory being used";
    		}
    		
    		leaf free-number {
    			type uint32;
    			description
    				"The number of free memory in kb";
    		}
    		
    		leaf free-percent {
    			type uint8;
    			description
    				"The percentage of free memory";
    		}
    		
    		leaf committed-number {
    			type uint32;
    			description
    				"The number of committed memory in kb";
    		}
    		
    		leaf committed-percent {
    			type uint8;
    			description
    				"The percentage of comitted memory";
    		}
    		
                container status {

    		leaf condition {
    			type string;
    			description
    				"Need description";
    		}
    		
    		leaf threshold-status {
    			type string;
    			description
    				"Need description";
    		}

                leaf threshold-value-percent {
                        type uint8;
                        description
                                "Need description";
		}

                }

                }
		
		container per-core-stats {
			description
				"Statistics on each core";
		
			list core {
				key "name";
				description
					"A Core";
					
	    		leaf name {
	    			type string;
	    			description
	    				"The name of the core";
	    		}
	    		
	    		leaf user {
	    			type decimal64 {
	    				fraction-digits 2;
	    			}
	    			description
	    				"The percentage of utilization by user";
	    		}
	    		
	    		leaf system {
	    			type decimal64 {
	    				fraction-digits 2;
	    			}
	    			description
	    				"The percentage of utilization by the system";
	    		}
	    		
	    		leaf nice {
	    			type decimal64 {
	    				fraction-digits 2;
	    			}
	    			description
	    				"The percentage of utilization by nice";
	    		}
	    		
	    		leaf idle {
	    			type decimal64 {
	    				fraction-digits 2;
	    			}
	    			description
	    				"The percentage that is idle";
	    		}
	    		
	    		leaf irq {
	    			type decimal64 {
	    				fraction-digits 2;
	    			}
	    			description
	    				"The percentage of utilizaion by irq";
	    		}
	    		
	    		leaf sirq {
	    			type decimal64 {
	    				fraction-digits 2;
	    			}
	    			description
	    				"The percentage of utilizaion by sirq";
	    		}
	    		
	    		leaf io-wait {
	    			type decimal64 {
	    				fraction-digits 2;
	    			}
	    			description
	    				"The percentage of utilization by IOwait";
	    		}
				
			}
		
		}
      	
                } 

	}

    container platform-software-interface-rp-active-brief-forwarding  {
        config false;
        description
            "DESCRIPTION NEEDED";
        
        list interface-xos {
            key "name";
            description
                "DESCRIPTION NEEDED";
        
            leaf name {
                type string;
                description
                    "DESCRPITION NEEDED";
            }
            
            leaf id {
                type uint64;
                description
                    "DESCRPITION NEEDED";
            }
            
            leaf qfp-id {
                type uint64;
                description
                    "DESCRPITION NEEDED";
            }
            
        }
        
    }

}
